// Generated by scripts/generate_vpp_microgrid.py.
// Households: 100. Edit the source template and regenerate.
package VPPMicrogrid {

    private import MetaModelDigitalTwin::*;

    #Component def GridTelemetry {
        // Power at the grid connection, in kW: positive for import into the
        // household, negative for export. Household reads this grid endpoint.
        #measureAttribute activePowerKW {
            :>> dataType default AttributeDataType::DOUBLE;
        }
        // Billing data published by Grid and read by CW. Its schema and
        // currency are unspecified in the diagram, so retain the raw data.
        #measureAttribute billingData {
            :>> dataType default AttributeDataType::STRING;
        }
    }

    #Component def HouseholdEnergySensor {
        // Cumulative energy charged from the grid into the household BESS.
        #measureAttribute chargedEnergyKWh {
            :>> dataType default AttributeDataType::DOUBLE;
        }
        // Cumulative energy discharged from the household BESS into the grid.
        #measureAttribute dischargedEnergyKWh {
            :>> dataType default AttributeDataType::DOUBLE;
        }
    }

    #Component def BatteryEnergyStorage {
        #measureAttribute stateOfChargePercent {
            :>> dataType default AttributeDataType::DOUBLE;
        }
        // Actual BESS power in kW: positive for charging, negative for discharge.
        #measureAttribute activePowerKW {
            :>> dataType default AttributeDataType::DOUBLE;
        }
        // Reports the power setpoint applied directly by the household
        // controller, using the same sign convention as activePowerKW.
        #measureAttribute powerSetpointKW {
            :>> dataType default AttributeDataType::DOUBLE;
        }
        // Reported operating mode, for example charging, discharging or idle.
        #measureAttribute operatingMode {
            :>> dataType default AttributeDataType::STRING;
        }
    }

    #Entity def GridConnection {
        // Logical data endpoint for the Grid box in the diagram.
        #component telemetry : GridTelemetry;
    }

    #Entity def HouseholdSite {
        #component Sensor : HouseholdEnergySensor;
        #component BESS : BatteryEnergyStorage;
    }

    #Entity def VPPService {
        // CW reads the existing Grid and Household endpoints. The diagram
        // does not show a separate CW sensor or a CW-to-BESS control link.
    }

    // The converter limits twin names to 10 characters; VPP has 3.
    #Twin def VPP {
        #entity Grid : GridConnection;
        #entity Household0001 : HouseholdSite;
        #entity Household0002 : HouseholdSite;
        #entity Household0003 : HouseholdSite;
        #entity Household0004 : HouseholdSite;
        #entity Household0005 : HouseholdSite;
        #entity Household0006 : HouseholdSite;
        #entity Household0007 : HouseholdSite;
        #entity Household0008 : HouseholdSite;
        #entity Household0009 : HouseholdSite;
        #entity Household0010 : HouseholdSite;
        #entity Household0011 : HouseholdSite;
        #entity Household0012 : HouseholdSite;
        #entity Household0013 : HouseholdSite;
        #entity Household0014 : HouseholdSite;
        #entity Household0015 : HouseholdSite;
        #entity Household0016 : HouseholdSite;
        #entity Household0017 : HouseholdSite;
        #entity Household0018 : HouseholdSite;
        #entity Household0019 : HouseholdSite;
        #entity Household0020 : HouseholdSite;
        #entity Household0021 : HouseholdSite;
        #entity Household0022 : HouseholdSite;
        #entity Household0023 : HouseholdSite;
        #entity Household0024 : HouseholdSite;
        #entity Household0025 : HouseholdSite;
        #entity Household0026 : HouseholdSite;
        #entity Household0027 : HouseholdSite;
        #entity Household0028 : HouseholdSite;
        #entity Household0029 : HouseholdSite;
        #entity Household0030 : HouseholdSite;
        #entity Household0031 : HouseholdSite;
        #entity Household0032 : HouseholdSite;
        #entity Household0033 : HouseholdSite;
        #entity Household0034 : HouseholdSite;
        #entity Household0035 : HouseholdSite;
        #entity Household0036 : HouseholdSite;
        #entity Household0037 : HouseholdSite;
        #entity Household0038 : HouseholdSite;
        #entity Household0039 : HouseholdSite;
        #entity Household0040 : HouseholdSite;
        #entity Household0041 : HouseholdSite;
        #entity Household0042 : HouseholdSite;
        #entity Household0043 : HouseholdSite;
        #entity Household0044 : HouseholdSite;
        #entity Household0045 : HouseholdSite;
        #entity Household0046 : HouseholdSite;
        #entity Household0047 : HouseholdSite;
        #entity Household0048 : HouseholdSite;
        #entity Household0049 : HouseholdSite;
        #entity Household0050 : HouseholdSite;
        #entity Household0051 : HouseholdSite;
        #entity Household0052 : HouseholdSite;
        #entity Household0053 : HouseholdSite;
        #entity Household0054 : HouseholdSite;
        #entity Household0055 : HouseholdSite;
        #entity Household0056 : HouseholdSite;
        #entity Household0057 : HouseholdSite;
        #entity Household0058 : HouseholdSite;
        #entity Household0059 : HouseholdSite;
        #entity Household0060 : HouseholdSite;
        #entity Household0061 : HouseholdSite;
        #entity Household0062 : HouseholdSite;
        #entity Household0063 : HouseholdSite;
        #entity Household0064 : HouseholdSite;
        #entity Household0065 : HouseholdSite;
        #entity Household0066 : HouseholdSite;
        #entity Household0067 : HouseholdSite;
        #entity Household0068 : HouseholdSite;
        #entity Household0069 : HouseholdSite;
        #entity Household0070 : HouseholdSite;
        #entity Household0071 : HouseholdSite;
        #entity Household0072 : HouseholdSite;
        #entity Household0073 : HouseholdSite;
        #entity Household0074 : HouseholdSite;
        #entity Household0075 : HouseholdSite;
        #entity Household0076 : HouseholdSite;
        #entity Household0077 : HouseholdSite;
        #entity Household0078 : HouseholdSite;
        #entity Household0079 : HouseholdSite;
        #entity Household0080 : HouseholdSite;
        #entity Household0081 : HouseholdSite;
        #entity Household0082 : HouseholdSite;
        #entity Household0083 : HouseholdSite;
        #entity Household0084 : HouseholdSite;
        #entity Household0085 : HouseholdSite;
        #entity Household0086 : HouseholdSite;
        #entity Household0087 : HouseholdSite;
        #entity Household0088 : HouseholdSite;
        #entity Household0089 : HouseholdSite;
        #entity Household0090 : HouseholdSite;
        #entity Household0091 : HouseholdSite;
        #entity Household0092 : HouseholdSite;
        #entity Household0093 : HouseholdSite;
        #entity Household0094 : HouseholdSite;
        #entity Household0095 : HouseholdSite;
        #entity Household0096 : HouseholdSite;
        #entity Household0097 : HouseholdSite;
        #entity Household0098 : HouseholdSite;
        #entity Household0099 : HouseholdSite;
        #entity Household0100 : HouseholdSite;
        #entity CW : VPPService;

        // Retention follows the existing microgrid examples.
        :>> hotDatabaseRetentionDays default 30;
        :>> coldDatabaseRetentionDays default 30;

        // Dependencies follow the read/control arrows in the diagram:
        // the client reads or controls the supplier, rather than sending
        // measurement data in the direction of the dependency arrow.
        dependency household0001ReadsGrid from Household0001 to Grid;
        dependency household0001ActuatesBESS from Household0001 to Household0001::BESS;
        dependency household0002ReadsGrid from Household0002 to Grid;
        dependency household0002ActuatesBESS from Household0002 to Household0002::BESS;
        dependency household0003ReadsGrid from Household0003 to Grid;
        dependency household0003ActuatesBESS from Household0003 to Household0003::BESS;
        dependency household0004ReadsGrid from Household0004 to Grid;
        dependency household0004ActuatesBESS from Household0004 to Household0004::BESS;
        dependency household0005ReadsGrid from Household0005 to Grid;
        dependency household0005ActuatesBESS from Household0005 to Household0005::BESS;
        dependency household0006ReadsGrid from Household0006 to Grid;
        dependency household0006ActuatesBESS from Household0006 to Household0006::BESS;
        dependency household0007ReadsGrid from Household0007 to Grid;
        dependency household0007ActuatesBESS from Household0007 to Household0007::BESS;
        dependency household0008ReadsGrid from Household0008 to Grid;
        dependency household0008ActuatesBESS from Household0008 to Household0008::BESS;
        dependency household0009ReadsGrid from Household0009 to Grid;
        dependency household0009ActuatesBESS from Household0009 to Household0009::BESS;
        dependency household0010ReadsGrid from Household0010 to Grid;
        dependency household0010ActuatesBESS from Household0010 to Household0010::BESS;
        dependency household0011ReadsGrid from Household0011 to Grid;
        dependency household0011ActuatesBESS from Household0011 to Household0011::BESS;
        dependency household0012ReadsGrid from Household0012 to Grid;
        dependency household0012ActuatesBESS from Household0012 to Household0012::BESS;
        dependency household0013ReadsGrid from Household0013 to Grid;
        dependency household0013ActuatesBESS from Household0013 to Household0013::BESS;
        dependency household0014ReadsGrid from Household0014 to Grid;
        dependency household0014ActuatesBESS from Household0014 to Household0014::BESS;
        dependency household0015ReadsGrid from Household0015 to Grid;
        dependency household0015ActuatesBESS from Household0015 to Household0015::BESS;
        dependency household0016ReadsGrid from Household0016 to Grid;
        dependency household0016ActuatesBESS from Household0016 to Household0016::BESS;
        dependency household0017ReadsGrid from Household0017 to Grid;
        dependency household0017ActuatesBESS from Household0017 to Household0017::BESS;
        dependency household0018ReadsGrid from Household0018 to Grid;
        dependency household0018ActuatesBESS from Household0018 to Household0018::BESS;
        dependency household0019ReadsGrid from Household0019 to Grid;
        dependency household0019ActuatesBESS from Household0019 to Household0019::BESS;
        dependency household0020ReadsGrid from Household0020 to Grid;
        dependency household0020ActuatesBESS from Household0020 to Household0020::BESS;
        dependency household0021ReadsGrid from Household0021 to Grid;
        dependency household0021ActuatesBESS from Household0021 to Household0021::BESS;
        dependency household0022ReadsGrid from Household0022 to Grid;
        dependency household0022ActuatesBESS from Household0022 to Household0022::BESS;
        dependency household0023ReadsGrid from Household0023 to Grid;
        dependency household0023ActuatesBESS from Household0023 to Household0023::BESS;
        dependency household0024ReadsGrid from Household0024 to Grid;
        dependency household0024ActuatesBESS from Household0024 to Household0024::BESS;
        dependency household0025ReadsGrid from Household0025 to Grid;
        dependency household0025ActuatesBESS from Household0025 to Household0025::BESS;
        dependency household0026ReadsGrid from Household0026 to Grid;
        dependency household0026ActuatesBESS from Household0026 to Household0026::BESS;
        dependency household0027ReadsGrid from Household0027 to Grid;
        dependency household0027ActuatesBESS from Household0027 to Household0027::BESS;
        dependency household0028ReadsGrid from Household0028 to Grid;
        dependency household0028ActuatesBESS from Household0028 to Household0028::BESS;
        dependency household0029ReadsGrid from Household0029 to Grid;
        dependency household0029ActuatesBESS from Household0029 to Household0029::BESS;
        dependency household0030ReadsGrid from Household0030 to Grid;
        dependency household0030ActuatesBESS from Household0030 to Household0030::BESS;
        dependency household0031ReadsGrid from Household0031 to Grid;
        dependency household0031ActuatesBESS from Household0031 to Household0031::BESS;
        dependency household0032ReadsGrid from Household0032 to Grid;
        dependency household0032ActuatesBESS from Household0032 to Household0032::BESS;
        dependency household0033ReadsGrid from Household0033 to Grid;
        dependency household0033ActuatesBESS from Household0033 to Household0033::BESS;
        dependency household0034ReadsGrid from Household0034 to Grid;
        dependency household0034ActuatesBESS from Household0034 to Household0034::BESS;
        dependency household0035ReadsGrid from Household0035 to Grid;
        dependency household0035ActuatesBESS from Household0035 to Household0035::BESS;
        dependency household0036ReadsGrid from Household0036 to Grid;
        dependency household0036ActuatesBESS from Household0036 to Household0036::BESS;
        dependency household0037ReadsGrid from Household0037 to Grid;
        dependency household0037ActuatesBESS from Household0037 to Household0037::BESS;
        dependency household0038ReadsGrid from Household0038 to Grid;
        dependency household0038ActuatesBESS from Household0038 to Household0038::BESS;
        dependency household0039ReadsGrid from Household0039 to Grid;
        dependency household0039ActuatesBESS from Household0039 to Household0039::BESS;
        dependency household0040ReadsGrid from Household0040 to Grid;
        dependency household0040ActuatesBESS from Household0040 to Household0040::BESS;
        dependency household0041ReadsGrid from Household0041 to Grid;
        dependency household0041ActuatesBESS from Household0041 to Household0041::BESS;
        dependency household0042ReadsGrid from Household0042 to Grid;
        dependency household0042ActuatesBESS from Household0042 to Household0042::BESS;
        dependency household0043ReadsGrid from Household0043 to Grid;
        dependency household0043ActuatesBESS from Household0043 to Household0043::BESS;
        dependency household0044ReadsGrid from Household0044 to Grid;
        dependency household0044ActuatesBESS from Household0044 to Household0044::BESS;
        dependency household0045ReadsGrid from Household0045 to Grid;
        dependency household0045ActuatesBESS from Household0045 to Household0045::BESS;
        dependency household0046ReadsGrid from Household0046 to Grid;
        dependency household0046ActuatesBESS from Household0046 to Household0046::BESS;
        dependency household0047ReadsGrid from Household0047 to Grid;
        dependency household0047ActuatesBESS from Household0047 to Household0047::BESS;
        dependency household0048ReadsGrid from Household0048 to Grid;
        dependency household0048ActuatesBESS from Household0048 to Household0048::BESS;
        dependency household0049ReadsGrid from Household0049 to Grid;
        dependency household0049ActuatesBESS from Household0049 to Household0049::BESS;
        dependency household0050ReadsGrid from Household0050 to Grid;
        dependency household0050ActuatesBESS from Household0050 to Household0050::BESS;
        dependency household0051ReadsGrid from Household0051 to Grid;
        dependency household0051ActuatesBESS from Household0051 to Household0051::BESS;
        dependency household0052ReadsGrid from Household0052 to Grid;
        dependency household0052ActuatesBESS from Household0052 to Household0052::BESS;
        dependency household0053ReadsGrid from Household0053 to Grid;
        dependency household0053ActuatesBESS from Household0053 to Household0053::BESS;
        dependency household0054ReadsGrid from Household0054 to Grid;
        dependency household0054ActuatesBESS from Household0054 to Household0054::BESS;
        dependency household0055ReadsGrid from Household0055 to Grid;
        dependency household0055ActuatesBESS from Household0055 to Household0055::BESS;
        dependency household0056ReadsGrid from Household0056 to Grid;
        dependency household0056ActuatesBESS from Household0056 to Household0056::BESS;
        dependency household0057ReadsGrid from Household0057 to Grid;
        dependency household0057ActuatesBESS from Household0057 to Household0057::BESS;
        dependency household0058ReadsGrid from Household0058 to Grid;
        dependency household0058ActuatesBESS from Household0058 to Household0058::BESS;
        dependency household0059ReadsGrid from Household0059 to Grid;
        dependency household0059ActuatesBESS from Household0059 to Household0059::BESS;
        dependency household0060ReadsGrid from Household0060 to Grid;
        dependency household0060ActuatesBESS from Household0060 to Household0060::BESS;
        dependency household0061ReadsGrid from Household0061 to Grid;
        dependency household0061ActuatesBESS from Household0061 to Household0061::BESS;
        dependency household0062ReadsGrid from Household0062 to Grid;
        dependency household0062ActuatesBESS from Household0062 to Household0062::BESS;
        dependency household0063ReadsGrid from Household0063 to Grid;
        dependency household0063ActuatesBESS from Household0063 to Household0063::BESS;
        dependency household0064ReadsGrid from Household0064 to Grid;
        dependency household0064ActuatesBESS from Household0064 to Household0064::BESS;
        dependency household0065ReadsGrid from Household0065 to Grid;
        dependency household0065ActuatesBESS from Household0065 to Household0065::BESS;
        dependency household0066ReadsGrid from Household0066 to Grid;
        dependency household0066ActuatesBESS from Household0066 to Household0066::BESS;
        dependency household0067ReadsGrid from Household0067 to Grid;
        dependency household0067ActuatesBESS from Household0067 to Household0067::BESS;
        dependency household0068ReadsGrid from Household0068 to Grid;
        dependency household0068ActuatesBESS from Household0068 to Household0068::BESS;
        dependency household0069ReadsGrid from Household0069 to Grid;
        dependency household0069ActuatesBESS from Household0069 to Household0069::BESS;
        dependency household0070ReadsGrid from Household0070 to Grid;
        dependency household0070ActuatesBESS from Household0070 to Household0070::BESS;
        dependency household0071ReadsGrid from Household0071 to Grid;
        dependency household0071ActuatesBESS from Household0071 to Household0071::BESS;
        dependency household0072ReadsGrid from Household0072 to Grid;
        dependency household0072ActuatesBESS from Household0072 to Household0072::BESS;
        dependency household0073ReadsGrid from Household0073 to Grid;
        dependency household0073ActuatesBESS from Household0073 to Household0073::BESS;
        dependency household0074ReadsGrid from Household0074 to Grid;
        dependency household0074ActuatesBESS from Household0074 to Household0074::BESS;
        dependency household0075ReadsGrid from Household0075 to Grid;
        dependency household0075ActuatesBESS from Household0075 to Household0075::BESS;
        dependency household0076ReadsGrid from Household0076 to Grid;
        dependency household0076ActuatesBESS from Household0076 to Household0076::BESS;
        dependency household0077ReadsGrid from Household0077 to Grid;
        dependency household0077ActuatesBESS from Household0077 to Household0077::BESS;
        dependency household0078ReadsGrid from Household0078 to Grid;
        dependency household0078ActuatesBESS from Household0078 to Household0078::BESS;
        dependency household0079ReadsGrid from Household0079 to Grid;
        dependency household0079ActuatesBESS from Household0079 to Household0079::BESS;
        dependency household0080ReadsGrid from Household0080 to Grid;
        dependency household0080ActuatesBESS from Household0080 to Household0080::BESS;
        dependency household0081ReadsGrid from Household0081 to Grid;
        dependency household0081ActuatesBESS from Household0081 to Household0081::BESS;
        dependency household0082ReadsGrid from Household0082 to Grid;
        dependency household0082ActuatesBESS from Household0082 to Household0082::BESS;
        dependency household0083ReadsGrid from Household0083 to Grid;
        dependency household0083ActuatesBESS from Household0083 to Household0083::BESS;
        dependency household0084ReadsGrid from Household0084 to Grid;
        dependency household0084ActuatesBESS from Household0084 to Household0084::BESS;
        dependency household0085ReadsGrid from Household0085 to Grid;
        dependency household0085ActuatesBESS from Household0085 to Household0085::BESS;
        dependency household0086ReadsGrid from Household0086 to Grid;
        dependency household0086ActuatesBESS from Household0086 to Household0086::BESS;
        dependency household0087ReadsGrid from Household0087 to Grid;
        dependency household0087ActuatesBESS from Household0087 to Household0087::BESS;
        dependency household0088ReadsGrid from Household0088 to Grid;
        dependency household0088ActuatesBESS from Household0088 to Household0088::BESS;
        dependency household0089ReadsGrid from Household0089 to Grid;
        dependency household0089ActuatesBESS from Household0089 to Household0089::BESS;
        dependency household0090ReadsGrid from Household0090 to Grid;
        dependency household0090ActuatesBESS from Household0090 to Household0090::BESS;
        dependency household0091ReadsGrid from Household0091 to Grid;
        dependency household0091ActuatesBESS from Household0091 to Household0091::BESS;
        dependency household0092ReadsGrid from Household0092 to Grid;
        dependency household0092ActuatesBESS from Household0092 to Household0092::BESS;
        dependency household0093ReadsGrid from Household0093 to Grid;
        dependency household0093ActuatesBESS from Household0093 to Household0093::BESS;
        dependency household0094ReadsGrid from Household0094 to Grid;
        dependency household0094ActuatesBESS from Household0094 to Household0094::BESS;
        dependency household0095ReadsGrid from Household0095 to Grid;
        dependency household0095ActuatesBESS from Household0095 to Household0095::BESS;
        dependency household0096ReadsGrid from Household0096 to Grid;
        dependency household0096ActuatesBESS from Household0096 to Household0096::BESS;
        dependency household0097ReadsGrid from Household0097 to Grid;
        dependency household0097ActuatesBESS from Household0097 to Household0097::BESS;
        dependency household0098ReadsGrid from Household0098 to Grid;
        dependency household0098ActuatesBESS from Household0098 to Household0098::BESS;
        dependency household0099ReadsGrid from Household0099 to Grid;
        dependency household0099ActuatesBESS from Household0099 to Household0099::BESS;
        dependency household0100ReadsGrid from Household0100 to Grid;
        dependency household0100ActuatesBESS from Household0100 to Household0100::BESS;

        // CW reads Grid.telemetry.billingData for billing.
        dependency cwReadsGridBilling from CW to Grid;

        // CW reads charged and discharged energy from every household Sensor.
        dependency cwReadsHousehold0001Energy from CW to Household0001;
        dependency cwReadsHousehold0002Energy from CW to Household0002;
        dependency cwReadsHousehold0003Energy from CW to Household0003;
        dependency cwReadsHousehold0004Energy from CW to Household0004;
        dependency cwReadsHousehold0005Energy from CW to Household0005;
        dependency cwReadsHousehold0006Energy from CW to Household0006;
        dependency cwReadsHousehold0007Energy from CW to Household0007;
        dependency cwReadsHousehold0008Energy from CW to Household0008;
        dependency cwReadsHousehold0009Energy from CW to Household0009;
        dependency cwReadsHousehold0010Energy from CW to Household0010;
        dependency cwReadsHousehold0011Energy from CW to Household0011;
        dependency cwReadsHousehold0012Energy from CW to Household0012;
        dependency cwReadsHousehold0013Energy from CW to Household0013;
        dependency cwReadsHousehold0014Energy from CW to Household0014;
        dependency cwReadsHousehold0015Energy from CW to Household0015;
        dependency cwReadsHousehold0016Energy from CW to Household0016;
        dependency cwReadsHousehold0017Energy from CW to Household0017;
        dependency cwReadsHousehold0018Energy from CW to Household0018;
        dependency cwReadsHousehold0019Energy from CW to Household0019;
        dependency cwReadsHousehold0020Energy from CW to Household0020;
        dependency cwReadsHousehold0021Energy from CW to Household0021;
        dependency cwReadsHousehold0022Energy from CW to Household0022;
        dependency cwReadsHousehold0023Energy from CW to Household0023;
        dependency cwReadsHousehold0024Energy from CW to Household0024;
        dependency cwReadsHousehold0025Energy from CW to Household0025;
        dependency cwReadsHousehold0026Energy from CW to Household0026;
        dependency cwReadsHousehold0027Energy from CW to Household0027;
        dependency cwReadsHousehold0028Energy from CW to Household0028;
        dependency cwReadsHousehold0029Energy from CW to Household0029;
        dependency cwReadsHousehold0030Energy from CW to Household0030;
        dependency cwReadsHousehold0031Energy from CW to Household0031;
        dependency cwReadsHousehold0032Energy from CW to Household0032;
        dependency cwReadsHousehold0033Energy from CW to Household0033;
        dependency cwReadsHousehold0034Energy from CW to Household0034;
        dependency cwReadsHousehold0035Energy from CW to Household0035;
        dependency cwReadsHousehold0036Energy from CW to Household0036;
        dependency cwReadsHousehold0037Energy from CW to Household0037;
        dependency cwReadsHousehold0038Energy from CW to Household0038;
        dependency cwReadsHousehold0039Energy from CW to Household0039;
        dependency cwReadsHousehold0040Energy from CW to Household0040;
        dependency cwReadsHousehold0041Energy from CW to Household0041;
        dependency cwReadsHousehold0042Energy from CW to Household0042;
        dependency cwReadsHousehold0043Energy from CW to Household0043;
        dependency cwReadsHousehold0044Energy from CW to Household0044;
        dependency cwReadsHousehold0045Energy from CW to Household0045;
        dependency cwReadsHousehold0046Energy from CW to Household0046;
        dependency cwReadsHousehold0047Energy from CW to Household0047;
        dependency cwReadsHousehold0048Energy from CW to Household0048;
        dependency cwReadsHousehold0049Energy from CW to Household0049;
        dependency cwReadsHousehold0050Energy from CW to Household0050;
        dependency cwReadsHousehold0051Energy from CW to Household0051;
        dependency cwReadsHousehold0052Energy from CW to Household0052;
        dependency cwReadsHousehold0053Energy from CW to Household0053;
        dependency cwReadsHousehold0054Energy from CW to Household0054;
        dependency cwReadsHousehold0055Energy from CW to Household0055;
        dependency cwReadsHousehold0056Energy from CW to Household0056;
        dependency cwReadsHousehold0057Energy from CW to Household0057;
        dependency cwReadsHousehold0058Energy from CW to Household0058;
        dependency cwReadsHousehold0059Energy from CW to Household0059;
        dependency cwReadsHousehold0060Energy from CW to Household0060;
        dependency cwReadsHousehold0061Energy from CW to Household0061;
        dependency cwReadsHousehold0062Energy from CW to Household0062;
        dependency cwReadsHousehold0063Energy from CW to Household0063;
        dependency cwReadsHousehold0064Energy from CW to Household0064;
        dependency cwReadsHousehold0065Energy from CW to Household0065;
        dependency cwReadsHousehold0066Energy from CW to Household0066;
        dependency cwReadsHousehold0067Energy from CW to Household0067;
        dependency cwReadsHousehold0068Energy from CW to Household0068;
        dependency cwReadsHousehold0069Energy from CW to Household0069;
        dependency cwReadsHousehold0070Energy from CW to Household0070;
        dependency cwReadsHousehold0071Energy from CW to Household0071;
        dependency cwReadsHousehold0072Energy from CW to Household0072;
        dependency cwReadsHousehold0073Energy from CW to Household0073;
        dependency cwReadsHousehold0074Energy from CW to Household0074;
        dependency cwReadsHousehold0075Energy from CW to Household0075;
        dependency cwReadsHousehold0076Energy from CW to Household0076;
        dependency cwReadsHousehold0077Energy from CW to Household0077;
        dependency cwReadsHousehold0078Energy from CW to Household0078;
        dependency cwReadsHousehold0079Energy from CW to Household0079;
        dependency cwReadsHousehold0080Energy from CW to Household0080;
        dependency cwReadsHousehold0081Energy from CW to Household0081;
        dependency cwReadsHousehold0082Energy from CW to Household0082;
        dependency cwReadsHousehold0083Energy from CW to Household0083;
        dependency cwReadsHousehold0084Energy from CW to Household0084;
        dependency cwReadsHousehold0085Energy from CW to Household0085;
        dependency cwReadsHousehold0086Energy from CW to Household0086;
        dependency cwReadsHousehold0087Energy from CW to Household0087;
        dependency cwReadsHousehold0088Energy from CW to Household0088;
        dependency cwReadsHousehold0089Energy from CW to Household0089;
        dependency cwReadsHousehold0090Energy from CW to Household0090;
        dependency cwReadsHousehold0091Energy from CW to Household0091;
        dependency cwReadsHousehold0092Energy from CW to Household0092;
        dependency cwReadsHousehold0093Energy from CW to Household0093;
        dependency cwReadsHousehold0094Energy from CW to Household0094;
        dependency cwReadsHousehold0095Energy from CW to Household0095;
        dependency cwReadsHousehold0096Energy from CW to Household0096;
        dependency cwReadsHousehold0097Energy from CW to Household0097;
        dependency cwReadsHousehold0098Energy from CW to Household0098;
        dependency cwReadsHousehold0099Energy from CW to Household0099;
        dependency cwReadsHousehold0100Energy from CW to Household0100;

        // The converter requires property references for both operands.
        // Self-equality triggers the mock without a stored threshold value.
        #condition mqttProbeReceived {
            :>> leftOperand = Household0001.BESS.activePowerKW;
            :>> operator = ComparisonOperator::EQUAL;
            :>> rightOperand = Household0001.BESS.activePowerKW;

            #strategyAction mqttProbe :>> strategieActions {
                :>> name = "mqttProbe";
                :>> strategyType = StrategyType::LAMBDA;
                :>> pathToCode = "/pipeline/code/vpp/mqtt-probe";
                :>> external = false;
                powerKW :>> inputParameters = Household0001.BESS.activePowerKW;
                :>> feedbackTopicType = FeedbackTopicType::EXTERN;
                :>> externalTopic = "VPP/evaluation/feedback";
            }
        }
    }
}
